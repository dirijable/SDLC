// SysML v2 Model: BarberBook
// Generated by SysML Web IDE
// 2026-10-18T10:44:00.910Z

package BarberBook {
  doc /* Модель структуры и ключевых требований системы онлайн-записи в барбер-шоп */
  
  private import ScalarValues;
  
  part def Client {
    doc /* Клиент: просматривает каталог, бронирует и отменяет свои записи */
  }
  
  part def Administrator {
    doc /* Администратор: управляет мастерами, услугами и расписанием */
  }
  
  enum def BookingStatus {
    upcoming;
    completed;
    cancelled;
  }
  
  part def Service {
    attribute name : String;
    
    attribute price : Natural;
    
    attribute durationHours : Natural = 1;
  }
  
  part def Master {
    attribute name : String;
    
    part services : Service [1..*];
  }
  
  part def Booking {
    attribute date : String;
    
    attribute hour : Natural;
    
    attribute status : BookingStatus;
    
    ref part client : Client;
    
    ref part master : Master;
    
    ref part service : Service;
  }
  
  part def CatalogModule {
    doc /* Каталог услуг и мастеров, фильтрация мастеров по выбранной услуге */
  }
  
  part def BookingModule {
    attribute workDayStart : Natural = 10;
    
    attribute workDayEnd : Natural = 20;
    
    attribute slotStepHours : Natural = 1;
  }
  
  part def WebInterface {
    doc /* Веб-страницы: каталог, выбор времени, мои записи, вход, панель администратора */
  }
  
  part def DataStorage {
    doc /* Хранение мастеров, услуг, пользователей и записей в PostgreSQL */
  }
  
  part def BarberBookApp {
    connect ui to catalog;
    connect ui to booking;
    connect catalog to storage;
    connect booking to storage;
    
    part catalog : CatalogModule;
    
    part booking : BookingModule;
    
    part ui : WebInterface;
    
    part storage : DataStorage;
  }
  
  part barberBook : BarberBookApp;
  
  use case def BrowseCatalog {
    subject app : BarberBookApp;
    
    actor client : Client;
  }
  
  use case def BookSlot {
    subject app : BarberBookApp;
    
    actor client : Client;
  }
  
  use case def CancelBooking {
    subject app : BarberBookApp;
    
    actor client : Client;
  }
  
  use case def ManageCatalog {
    subject app : BarberBookApp;
    
    actor admin : Administrator;
  }
  
  package Requirements {
    private import ScalarValues;
    
    requirement def DarkStyle {
      doc /* Система должна отображать интерфейс в тёмном стиле оформления */
    }
    
    requirement def DefaultCatalog {
      doc /* При первом запуске система должна загружать мастеров и услуги по умолчанию */
    }
    
    requirement def MaxSteps {
      doc /* Запись на услугу должна выполняться не более чем за три шага */
      
      attribute maxSteps : Natural = 3;
    }
    
    requirement def NoDoubleBooking {
      doc /* Система не должна допускать двух записей одного мастера на один слот */
    }
    
    requirement darkStyle : DarkStyle {
      attribute reqId : String = "REQ-INT-001";
    }
    
    requirement def aultCatalog {
      attribute reqId : String = "REQ-FUNC-001";
    }
    
    requirement noDoubleBooking : NoDoubleBooking {
      attribute reqId : String = "REQ-FUNC-007";
    }
    
    requirement threeSteps : MaxSteps {
      attribute reqId : String = "REQ-FUNC-013";
    }
  }
}
